module sal-queue {
    namespace "urn:opendaylight:queue:service";
    prefix queue;

    import opendaylight-inventory {prefix inv; revision-date "2013-08-19";}
    import opendaylight-queue-types {prefix queue-type; revision-date "2013-09-25";}

    revision "2013-11-07" {
        description "Initial revision of queue service";
    }        

    rpc get-queue {
        output {
            uses queue-type:queue-packet;
        }
    }  
    
}
