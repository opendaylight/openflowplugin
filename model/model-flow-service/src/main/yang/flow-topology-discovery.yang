module flow-topology-discovery {
    namespace "urn:opendaylight:flow:topology:discovery";
    prefix flow-node-topo;

    import opendaylight-inventory {prefix inv;revision-date "2013-08-19";}

    description "Legacy topology API.";
    
    revision "2013-08-19" {
        description "Flow Capable Node extensions to the Inventory model";
    }
    

    grouping link {
        leaf source {
            type inv:node-connector-ref;
        }
        leaf destination {
            type inv:node-connector-ref;
        }
    }

    notification link-discovered {
        status deprecated;
        uses link;
    }
    
    notification link-overutilized {
        status deprecated;
        uses link;
    }
    
    notification link-removed {
        status deprecated;
        uses link;
    }

    notification link-utilization-normal {
        status deprecated;
        uses link;
    }

    rpc solicit-refresh {
        status deprecated;
    }

}
