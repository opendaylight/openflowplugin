module sal-echo {
    namespace "urn:opendaylight:echo:service";
    prefix echo;

    import opendaylight-inventory {prefix inv; revision-date "2013-08-19";}

    description "Openflow echo service.";

    revision "2015-03-05" {
        description "Initial proposal, tentative API.";
    }
    
    rpc send-echo {
        description "Sending echo message to openflow device.";

        input {
            uses "inv:node-context-ref";
            leaf data {
                description "Openflow echo request payload (arbirary-length data ﬁeld). The
                  data ﬁeld might be a message timestamp to check latency, various lengths
                  to measure bandwidth, or zero-size to verify liveness between the switch 
                  and controller.";

                type binary;
            }
        }
        output {
            leaf data {
                description "Unmodified data field.";

                type binary;
            }
        }
    }  
}
