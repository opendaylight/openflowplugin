module cisco-action-high {
    yang-version 1;

    namespace "urn:opendaylight:openflowplugin:extension:cof:hi:action";
    prefix "cisco-action-high";

    import ietf-inet-types {prefix inet;}
    import ietf-yang-types {prefix yang;}
    import yang-ext {prefix ext; revision-date "2013-07-09";}

    description 
        "Cisco openflow extensions of action - semantic view.";

    revision "2014-10-10" {
        description "Initial revision";
    }
    

    // output next hop ----
    typedef cof-at-output-nh-address-type {
        type enumeration {
            enum NONE {
                description "address only";
            }
            enum P2P {
                description "address and port";
            }
            enum IPV4 {
                description "address and port";
            }
            enum IPV6 {
                description "address and port";
            }
            enum MAC48 {
                description "address and port";
            }
        }
    }
    
    typedef cof-at-output-nh-address-extra-type {
        type enumeration {
            enum NONE {
                description "address only";
            }
            enum PORT {
                description "address and port";
            }
        }
    }
    
    typedef nh-port-number {
        type uint32;
    }
    
    grouping cof-action-next-hop-grouping {
        container action-output-nh-hi {
        
            leaf address-type {
                type cof-at-output-nh-address-type;
            }
            leaf address-extra-type {
                type cof-at-output-nh-address-extra-type;
            }
            
            leaf address-nh {
                type union {
                    type inet:ipv4-address;
                    type inet:ipv6-address;
                    type yang:mac-address;
                } 
            }
            leaf address-extra {
                type nh-port-number;
            }
        }
    }
    // mpls
    typedef mpls-lsp-name {
        type string;
    }

    grouping cof-action-mpls-lsp-grouping {
        container action-mpls-lsp-hi {
            leaf mpls-lsp-name {
                type mpls-lsp-name;
            }
        }
    }
    // netflow
    grouping cof-action-netflow-grouping {
        container action-netflow-hi {
            leaf netflow {
                type empty;
            }
        }
    }
    // fcid
    typedef fcid-id {
        type uint16;
    }
    grouping cof-action-fcid-grouping {
        container action-fcid-hi {
            leaf fcid {
                type fcid-id;
            }
        }
    }
    // vrf ----
    typedef cof-at-vrf-type {
        type enumeration {
            enum NONE {
                description "illegal value";
            }
            enum VPNID {
                description "vpn-id (rfc 2685)";
            }
            enum NAME {
                description "vrf namestring (sized determine by len)";
            }
        }
    }
    
    typedef vrf-vpn-id {
        description "see RFC-2685, vpn identifier (7 bytes)";
        type binary;
    }
    typedef vrf-name {
        type string;
    }
    typedef vrf-extra {
        type union {
            type vrf-vpn-id;
            type vrf-name;
        }
    }
    
    grouping cof-action-vrf-grouping {
        container action-vrf-hi {
            leaf vpn-type {
                type cof-at-vrf-type;
            }
            leaf vrf-extra {
                type vrf-extra;
            }
        }
    }
}
