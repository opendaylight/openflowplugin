module cisco-extension {
	yang-version 1;
    namespace "urn:opendaylight:params:xml:ns:yang:controller:config:openflowplugin:cof:config";
    prefix "ciscoExt-cfg";

    import config {prefix config; revision-date 2013-04-05; }

    description
        "openflow extension for cisco - config";

    revision "2014-10-10" {
        description
            "Initial revision";
    }

    identity cisco-extension-provider {
        base config:service-type;
        config:java-class "org.opendaylight.openflowplugin.extension.vendor.cisco.CiscoExtensionProvider";
    }
}
