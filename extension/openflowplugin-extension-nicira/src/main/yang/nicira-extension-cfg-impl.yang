module nicira-extension-impl {
	yang-version 1;
    namespace "urn:opendaylight:params:xml:ns:yang:openflowplugin:nx:config:impl";
    prefix "niciraExt-cfg-impl";

    import config {prefix config; revision-date 2013-04-05;}
    import openflowplugin-extension-registry {prefix ofp-ext-reg; revision-date 2015-04-25;}
    import nicira-extension {prefix niciraExt-provider;}

    description
        "openflow extension for nicira - config-impl";

    revision "2014-07-11" {
        description
            "Initial revision";
    }

    identity nicira-extension-provider-impl {
        base config:module-type;
        config:provided-service niciraExt-provider:nicira-extension-provider;
        config:java-name-prefix ConfigurableNiciraExtensionProvider;
    }

    augment "/config:modules/config:module/config:configuration" {
        case nicira-extension-provider-impl {
            when "/config:modules/config:module/config:type = 'nicira-extension-provider-impl'";

            container openflow-plugin-extension-registry {
                uses config:service-ref {
                    refine type {
                        mandatory true;
                        config:required-identity ofp-ext-reg:openflow-extension-registry-provider;
                    }
                }
            }
        }
    }
}
