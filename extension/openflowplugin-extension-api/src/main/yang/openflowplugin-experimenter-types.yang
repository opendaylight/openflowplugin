module openflowplugin-experimenter-types {
    namespace "urn:opendaylight:openflowplugin:experimenter:types";
    prefix exp-type;

    import opendaylight-multipart-types { prefix multipart; revision-date "2017-01-12"; }

    revision "2015-10-20" {
        description "Initial revision of experimenter basic types";
    }


    grouping experimenter-core-message {
        choice experimenter-message-of-choice {
            // to be augmented by vendors
        }
    }

    augment "/multipart:multipart-reply/multipart:multipart-reply-body" {
        case multipart-reply-experimenter {
            uses experimenter-core-message;
        }
    }

}
