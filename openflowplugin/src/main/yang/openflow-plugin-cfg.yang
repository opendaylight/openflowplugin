module openflow-provider {
	yang-version 1;
    namespace "urn:opendaylight:params:xml:ns:yang:openflow:common:config";
    prefix "ofplugin-cfg";

    import config {prefix config; revision-date 2013-04-05; }

    description
        "openflow-plugin-custom-config";

    revision "2014-03-26" {
        description
            "Initial revision";
    }

    identity openflow-provider{
        base config:service-type;
        config:java-class "org.opendaylight.openflowplugin.openflow.md.core.sal.OpenflowPluginProvider";
        config:disable-osgi-service-registration;
    }
}
