module openflow-provider-impl {
	yang-version 1;
    namespace "urn:opendaylight:params:xml:ns:yang:openflow:common:config:impl";
    prefix "ofplugin-cfg-impl";

    description
        "openflow-plugin-custom-config-impl";

    revision "2014-03-26" {
        description
            "Initial revision";
    }

    // role of OFPlugin instance
    typedef ofp-role {
        type enumeration {
            enum NOCHANGE {
                description "no change to role";
            }
            enum BECOMEMASTER {
                description "promote current role to MASTER";
            }
            enum BECOMESLAVE {
                description "demote current role to SLAVE";
            }
        }
    }

}
