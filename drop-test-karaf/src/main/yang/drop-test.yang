module drop-test-provider {
	yang-version 1;
    namespace "urn:opendaylight:params:xml:ns:yang:config:openflow:test:droptest";
    prefix "drop-test-provider";

    import config {prefix config; revision-date 2013-04-05;}
    import rpc-context { prefix rpcx; revision-date 2013-06-17; }
    import opendaylight-md-sal-binding { prefix md-sal-binding; revision-date 2013-10-28;}
    import opendaylight-sal-binding-broker-impl { prefix sal-broker; revision-date 2013-10-28;}

    description
        "drop-test-provider";

    revision "2015-03-27" {
        description
            "Drop test implementation.";
    }

    identity drop-test-provider {
        base config:module-type;
        config:java-name-prefix DropTestProvider;
    }

    augment "/config:modules/config:module/config:configuration" {
        case drop-test-provider {
            when "/config:modules/config:module/config:type = 'drop-test-provider'";

            container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-adapter {
                uses config:service-ref {
                    refine type {
                        mandatory true;
                        config:required-identity sal-broker:binding-new-notification-service;
                    }
                }
            }
            leaf mul {
                type ofp-types:ofp-role;
                default "NOCHANGE";
            }
        }
    }
}
