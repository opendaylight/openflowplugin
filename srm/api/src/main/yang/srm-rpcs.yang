module srm-rpcs {
    namespace "urn:opendaylight:serviceutils:srm:rpcs";
    prefix "srmrpcs";

    import srm-types {
        prefix srmtype;
    }

    revision "2017-07-11" {
        description "ODL Services Recovery Manager Rpcs Module";
    }

    /* RPCs */

    rpc reinstall {
        description "Reinstall a given service";
        input {
            leaf entity-name {
                type identityref {
                    base srmtype:entity-name-base;
                }
            }
            leaf entity-type {
                description "Currently supported entity-types:
                                service";
                type identityref {
                    base srmtype:entity-type-base;
                }
            }
        }
        output {
            leaf successful {
                type boolean;
            }
            leaf message {
                type string;
            }
        }
    }


    rpc recover {
        description "Recover a given service or instance";
        input {
            leaf entity-name {
                type identityref {
                    base srmtype:entity-name-base;
                }
            }
            leaf entity-type {
                description "Currently supported entity-types:
                                service, instance";
                type identityref {
                    base srmtype:entity-type-base;
                }
            }
            leaf entity-id {
                description "Optional when entity-type is service. Actual
                             id depends on entity-type and entity-name";
                type string;
            }
        }
        output {
            leaf response {
                type identityref {
                    base rpc-result-base;
                }
            }
            leaf message {
                type string;
            }
        }
    }

    /* RPC RESULTs */

    identity rpc-result-base {
        description "Base identity for all SRM RPC Results";
    }
    identity rpc-success {
        description "RPC result successful";
        base rpc-result-base;
    }
    identity rpc-fail-op-not-supported {
        description "RPC failed:
                        operation not supported for given parameters";
        base rpc-result-base;
    }
    identity rpc-fail-entity-type {
        description "RPC failed:
                        invalid entity type";
        base rpc-result-base;
    }
    identity rpc-fail-entity-name {
        description "RPC failed:
                        invalid entity name";
        base rpc-result-base;
    }
    identity rpc-fail-entity-id {
        description "RPC failed:
                        invalid entity id";
        base rpc-result-base;
    }
    identity rpc-fail-unknown {
        description "RPC failed:
                        reason not known, check message string for details";
        base rpc-result-base;
    }
}
