module flowprogrammer-impl {
    yang-version 1;
    namespace "urn:opendaylight:params:xml:ns:yang:openflowplugin:flowprogrammer:impl";
    prefix "flowprogrammer-impl";

    import config { prefix config; revision-date 2013-04-05; }
    import opendaylight-md-sal-binding { prefix md-sal-binding; revision-date 2013-10-28;}

    description
        "This module contains the base YANG definitions for flowprogrammer impl";

    revision "2015-09-14" {
        description
            "Initial revision";
    }

    identity flowprogrammer-impl {
        base config:module-type;
        config:java-name-prefix FlowProgrammerImpl;
    }

    augment "/config:modules/config:module/config:configuration" {
        case flowprogrammer-impl {
            when "/config:modules/config:module/config:type = 'flowprogrammer-impl'";
            //wires in the data-broker service
            container data-broker {
                uses config:service-ref {
                    refine type {
                        mandatory false;
                        config:required-identity md-sal-binding:binding-async-data-broker;
                    }
                }
            }
        }
    }
}
