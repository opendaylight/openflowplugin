module prioritytaskmgr-api {
	yang-version 1;
    namespace "urn:opendaylight:params:xml:ns:yang:openflow:applications:prioritytaskmgr:api";
    prefix "priotaskmgr-api";

    import config { prefix config; revision-date 2013-04-05; }

    description
        "Service definition for priority task manager";

    revision "2016-02-10" {
        description
            "Initial revision";
    }

    identity prioritytaskmgr-api {
        base "config:service-type";
        config:java-class "org.opendaylight.openflowplugin.applications.prioritytaskmgr.api.IPriorityTaskManager";
    }
}
