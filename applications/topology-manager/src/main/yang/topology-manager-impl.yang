module topology-manager-impl {
    yang-version 1;
    namespace "urn:opendaylight:params:xml:ns:yang:topology-manager:impl";
    prefix "topology-manager-impl";

    import config { prefix config; revision-date 2013-04-05; }
    import opendaylight-md-sal-binding { prefix md-sal-binding; revision-date 2013-10-28;}

    description
        "Service definition for topology-manager";

    revision "2015-05-30" {
        description
            "Initial revision";
    }

    identity topology-manager-impl {
        base config:module-type;
        config:java-name-prefix TopologyLldpDiscoveryImpl;
        status deprecated;
    }

    augment "/config:modules/config:module/config:configuration" {
        case topology-manager-impl {
            when "/config:modules/config:module/config:type = 'topology-manager-impl'";
            container broker {
                uses config:service-ref {
                    refine type {
                        mandatory true;
                        config:required-identity md-sal-binding:binding-broker-osgi-registry;
                    }
                }
            }
        }
    }
}
