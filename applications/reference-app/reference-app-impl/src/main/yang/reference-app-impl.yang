module reference-app-impl {
    yang-version 1;
    namespace "urn:opendaylight:params:xml:ns:yang:reference-app:impl";
    prefix "reference-app-impl";
    import config {prefix config; revision-date 2013-04-05;}
    import opendaylight-md-sal-binding { prefix mdsal; revision-date 2013-10-28;}
    import southboundmanager-api { prefix sbmgr-api; revision-date 2016-02-10;}
    import prioritytaskmgr-api {prefix priotaskmgr-api; revision-date 2016-02-10;}

    description
        "Reference app project";

    revision "2016-02-10" {
        description
            "Initial revision";
    }

    identity reference-app-impl {
        base "config:module-type";
        config:java-name-prefix ReferenceApp;
    }

    augment "/config:modules/config:module/config:configuration" {
        case reference-app-impl {
            when "/config:modules/config:module/config:type = 'reference-app-impl'";
            container osgi-broker {
                uses config:service-ref {
                    refine type {
                        mandatory true;
                        config:required-identity mdsal:binding-broker-osgi-registry;
                    }
                }
            }
            container rpc-registry {
                uses config:service-ref {
                    refine type {
                        mandatory true;
                        config:required-identity mdsal:binding-rpc-registry;
                    }
                }
            }
            container data-broker {
                uses config:service-ref {
                    refine type {
                        mandatory true;
                        config:required-identity mdsal:binding-async-data-broker;
                    }
                }
            }
            container southboundmanager {
                uses config:service-ref {
                    refine type {
                        mandatory true;
                        config:required-identity sbmgr-api:southboundmanager-api;
                    }
                }
            }
            container prioritytaskmgr {
                uses config:service-ref {
                    refine type {
                        mandatory true;
                        config:required-identity priotaskmgr-api:prioritytaskmgr-api;
                    }
                }

            }

        }
    }
}
