module table-miss-enforcer {
	yang-version 1;
    namespace "urn:opendaylight:params:xml:ns:yang:openflow:applications:table-miss-enforcer";
    prefix "table-miss-enforcer";
    import config {prefix config; revision-date 2013-04-05;}
    import opendaylight-md-sal-binding { prefix mdsal; revision-date 2013-10-28; }

    description
        "table-miss-enforcer-custom-config-impl";

    revision "2014-03-26" {
        description
            "Initial revision";
    }

    identity table-miss-enforcer {
        base "config:module-type";
        config:java-name-prefix LLDPPacketPuntEnforcer;
        status deprecated;
    }

    augment "/config:modules/config:module/config:configuration" {
        case table-miss-enforcer {
            when "/config:modules/config:module/config:type = 'table-miss-enforcer'";
            container rpc-registry {
                uses config:service-ref {
                    refine type {
                        mandatory true;
                        config:required-identity mdsal:binding-rpc-registry;
                    }
                }
            }
            container data-broker {
                uses config:service-ref {
                    refine type {
                        mandatory false;
                        config:required-identity mdsal:binding-async-data-broker;
                    }
                }
            }
        }
    }
}
