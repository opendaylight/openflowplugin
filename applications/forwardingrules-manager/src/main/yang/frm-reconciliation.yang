module frm-reconciliation {
    namespace "urn:opendaylight:params:xml:ns:yang:openflowplugin:app:frm-reconciliation:service";
    prefix frm-reconciliation;

    import ietf-yang-types { prefix yang; }
    import opendaylight-inventory { prefix inv; }

    revision "2018-02-27" {
        description "Initial revision of trigger based frm reconciliation";
    }

    rpc reconcile-node {
        description "Executes reconciliation between the controller and node";
        input {
            uses "inv:node-context-ref";
            leaf nodeId {
                type uint64;
            }
        }

        output {
            leaf result {
                description "The result of reconciliation, for follow-up";
                type boolean;
            }
        }
    }

    augment /inv:nodes/inv:node {
        container frm-reconciliation {
            leaf success-count {
                type uint32;
                default 0;
            }
            leaf failure-count {
                type uint32;
                default 0;
            }
            leaf last-request-time {
                description "Timestamp when reconciliation was last requested";
                type yang:date-and-time;
            }
        }
    }
}
