module forwardingrules-manager {

    yang-version 1;
    namespace "urn:opendaylight:params:xml:ns:yang:openflowplugin:app:forwardingrules-manager";
    prefix "frm";

    import config { prefix config; revision-date 2013-04-05; }
    import opendaylight-md-sal-binding { prefix mdsal; revision-date 2013-10-28; }
    import opendaylight-entity-ownership-service { prefix eos; }

    description
        "This module contains the base YANG definitions for
        forwardingrules-manager implementation.";

    revision "2014-09-25" {
        description
            "Initial revision.";
    }

    identity forwardingrules-manager {
            base config:module-type;
            config:java-name-prefix ForwardingRulesManager;
            status deprecated;
    }

    augment "/config:modules/config:module/config:configuration" {
        case forwardingrules-manager {
            when "/config:modules/config:module/config:type = 'forwardingrules-manager'";

            container rpc-registry {
                uses config:service-ref {
                    refine type {
                        mandatory true;
                        config:required-identity mdsal:binding-rpc-registry;
                    }
                }
            }

            container data-broker {
                uses config:service-ref {
                    refine type {
                        mandatory false;
                        config:required-identity mdsal:binding-async-data-broker;
                    }
                }
            }

            container forwarding-manager-settings {
                leaf stale-marking-enabled {
                    type boolean;
                }
		leaf reconciliation-retry-count {
	             type uint16;
	        }

            }

            container entity-ownership-service {
                uses config:service-ref {
                    refine type {
                        mandatory true;
                            config:required-identity eos:entity-ownership-service;
                    }
                }
            }

        }
    }

}
