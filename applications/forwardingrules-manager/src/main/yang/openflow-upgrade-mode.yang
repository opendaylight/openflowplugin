module openflow-upgrade {
    yang-version 1;
    namespace "urn:opendaylight:params:xml:ns:yang:openflow:upgrade";
    prefix "openflow-upgrade";

    import opendaylight-inventory {prefix inv; revision-date "2013-08-19";}

    description
        "Flag to determine whether upgrade is in progress";

    revision "2018-03-28" {
        description
            "Initial proposal.";
    }

    container upgrade-progress {
        leaf upgrade-in-progress {
            description "Is upgrade in process.";
            type boolean;
        }
    }

     rpc finish-upgrade-reconciliation-nodes {
                description "Stops the upgrade reconciliation for a list nodes or all the connected nodes";
                input {
                    uses "inv:node-context-ref";
                    leaf-list nodes {
                        description "List of nodes for which the upgrade reconciliation has to be stopped";
                        type uint64;
                    }

                    leaf finish-upgrade-all-nodes {
                        description "Flag to indicate that upgrade reconciliation has to be stopped for all nodes";
                        type boolean;
                        mandatory false;
                        default false;
                    }
                }

                output {
                     leaf result {
                         type boolean;
                     }
                }
     }
}
