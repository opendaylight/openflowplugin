module of-switch-config-pusher {
	yang-version 1;
    namespace "urn:opendaylight:params:xml:ns:yang:openflow:applications:of-switch-config-pusher";
    prefix "of-switch-config-pusher";
    import config {prefix config; revision-date 2013-04-05;}
    import opendaylight-md-sal-binding { prefix mdsal; revision-date 2013-10-28; }

    description
        "of-switch-config-pusher-custom-config-impl";

    revision "2014-10-15" {
        description
            "Initial revision";
    }

    identity of-switch-config-pusher {
        base "config:module-type";
        config:java-name-prefix DefaultConfigPusher;
        status deprecated;
    }

    augment "/config:modules/config:module/config:configuration" {
        case of-switch-config-pusher {
            when "/config:modules/config:module/config:type = 'of-switch-config-pusher'";
            container rpc-registry {
                uses config:service-ref {
                    refine type {
                        mandatory true;
                        config:required-identity mdsal:binding-rpc-registry;
                    }
                }
            }
            container data-broker {
                uses config:service-ref {
                    refine type {
                        mandatory false;
                        config:required-identity mdsal:binding-async-data-broker;
                    }
                }
            }
        }
    }
}
