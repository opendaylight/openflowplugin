module bulk-o-matic {
    yang-version 1;
    namespace "urn:opendaylight:params:xml:ns:yang:openflow:applications:bulk-o-matic";
    prefix "bulk";
    import config {prefix config; revision-date 2013-04-05;}
    import opendaylight-md-sal-binding { prefix mdsal; revision-date 2013-10-28;}
    import opendaylight-entity-ownership-service { prefix entity-ownership-service; }

    description
        "End point application providing bulk operation via DS and via rpc";

    revision "2015-06-08" {
        description
            "Initial revision";
    }

    identity bulk-o-matic {
        base "config:module-type";
        config:java-name-prefix BulkOMatic;
        status deprecated;
    }

    augment "/config:modules/config:module/config:configuration" {
        case bulk-o-matic {
            when "/config:modules/config:module/config:type = 'bulk-o-matic'";
            container rpc-registry {
                uses config:service-ref {
                    refine type {
                        mandatory true;
                        config:required-identity mdsal:binding-rpc-registry;
                    }
                }
            }
            container data-broker {
                uses config:service-ref {
                    refine type {
                        mandatory false;
                        config:required-identity mdsal:binding-async-data-broker;
                    }
                }
            }
        }
    }
}
