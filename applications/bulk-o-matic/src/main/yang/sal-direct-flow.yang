module sal-bulk-flow-direct {
    namespace "urn:opendaylight:bulk-flow-direct:service";
    prefix bflowdirect;

    import sal-bulk-flow { prefix bflow; revision-date "2015-06-08"; }

    revision "2016-10-11" {
        description "Initial revision of direct statistics service";
    }

    rpc flow-rpc-add-test {
    	input {
    	    leaf dpn-id {
                type string;
                mandatory true;
                status current;
                description "DPID to which flows are pushed";
            }

            leaf flow-count {
                type uint32;
                mandatory true;
                status current;
                description "Flows to be pushed per DPN";
            }

            leaf rpc-batch-size {
                type uint32;
                mandatory true;
                status current;
                description "Batch-size which would be sent continuously without any pause, If less than sal-bulk-flow:flow-count, a fixed pause of 40 ms would be introduced";
            }
        }
    }

    rpc flow-rpc-add-multiple {
    	input {
    	    leaf flow-count {
                type uint32;
                mandatory true;
                status current;
                description "Flows to be pushed per DPN";
            }

            leaf rpc-batch-size {
                type uint32;
                mandatory true;
                status current;
                description "Batch-size which would be sent continuously without any pause, If less than sal-bulk-flow:flow-count, a fixed pause of 40 ms would be introduced";
    	    }
        }
    }
}
