module openflow-upgrade-mode {
	yang-version 1;
    namespace "urn:opendaylight:params:xml:ns:yang:openflow:upgrade:mode";
    prefix "openflow-upgrade-mode";

    description
        "Upgrade mode";

    revision "2018-03-28" {
        description
            "Initial proposal.";
    }

    typedef mode {
        type enumeration {
            enum AUTONOMOUS {
                description "The flows and groups are pushed as flow and group mods";
            }
            enum ARBITER {
                description "The flows and groups are pushed as bundles";
            }
        }
        default "AUTONOMOUS";
    }

    container openflow-upgrade-mode {
        leaf upgrade-mode {
            description "Upgrade mode.";
            type mode ;
        }
    }
}
