module jobcoordinator-api {
    yang-version 1;
    namespace "urn:opendaylight:params:xml:ns:yang:openflow:applications:jobcoordinator:api";
    prefix "jobcoordinator-api";

    import config { prefix config; revision-date 2013-04-05; }

    description
        "Job Coordinator Service module";

    revision "2016-02-25" {
        description
            "Initial revision";
    }

    identity jobcoordinator-api {
        base "config:service-type";
        config:java-class "org.opendaylight.openflowplugin.applications.jobcoordinator.api.IJobCoordinator";
    }
}
