module inventory-manager-impl {
    yang-version 1;
    namespace "urn:opendaylight:params:xml:ns:yang:inventory-manager:impl";
    prefix "inventory-manager-impl";

    import config { prefix config; revision-date 2013-04-05; }
    import opendaylight-md-sal-binding { prefix md-sal-binding; revision-date 2013-10-28;}
    import opendaylight-entity-ownership-service { prefix eos; }

    description
        "Service definition for inventory manager";

    revision "2015-05-30" {
        description
            "Initial revision";
    }

    identity inventory-manager-impl {
        base config:module-type;
        config:java-name-prefix InventoryManagerImpl;
        status deprecated;
    }

    augment "/config:modules/config:module/config:configuration" {
        case inventory-manager-impl {
            when "/config:modules/config:module/config:type = 'inventory-manager-impl'";
            container broker {
                uses config:service-ref {
                    refine type {
                        mandatory true;
                        config:required-identity md-sal-binding:binding-broker-osgi-registry;
                    }
                }
            }

            container entity-ownership-service {
                uses config:service-ref {
                    refine type {
                        mandatory true;
                        config:required-identity eos:entity-ownership-service;
                    }
                }
            }
        }
    }
}
