module lldp-speaker {
    yang-version 1;
    namespace "urn:opendaylight:params:xml:ns:yang:openflow:applications:lldp-speaker";
    prefix "lldp-speaker";

    description
        "Application that send LLDPDU frames to all Openflow switch ports.";

    revision "2014-10-23" {
        description
            "Initial revision";
    }

    typedef oper-status {
        type enumeration {
            enum STANDBY {
                description "go to stand by mode";
            }
            enum RUN {
                description "go to fully operational mode";
            }
        }
    }

    rpc change-operational-status {
        input {
            leaf operational-status {
                type oper-status;
                description "Change operational status of LLDP speaker.";
            }
         }
    }
    rpc get-operational-status {
        output {
            leaf operational-status {
                type oper-status;
                description "Change operational status of LLDP speaker.";
            }
         }
    }
    rpc set-lldp-flood-interval {
        input {
            leaf set-interval {
               type int64;
               description "Set LLDP_FLOOD_PERIOD";
            }
        }
    }
    rpc get-lldp-flood-interval {
        output {
            leaf get-interval {
               type int64;
               description "Get LLDP_FLOOD_PERIOD";
            }
        }
    }
}
