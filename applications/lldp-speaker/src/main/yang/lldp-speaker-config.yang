module lldp-speaker-config {
    yang-version 1;
    namespace "urn:opendaylight:params:xml:ns:yang:openflow:applications:lldp-speaker:config";
    prefix "lldp-speaker-config";

    import ietf-yang-types {prefix yang; revision-date "2010-09-24";}

    description
        "Configuration for LLDP speaker application.";

    revision "2016-05-12" {
        description
            "Initial revision.";
    }

    container lldp-speaker-config {
        leaf address-destination {
            type yang:mac-address;
            mandatory true;
        }
    }
}
