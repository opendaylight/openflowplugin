module southboundmanager-api {
    yang-version 1;
    namespace "urn:opendaylight:params:xml:ns:yang:openflow:applications:southboundmanager:api";
    prefix "southboundmanager-api";

    import config { prefix config; revision-date 2013-04-05; }

    description
        "Southbound Manager Service module";

    revision "2016-02-10" {
        description
            "Initial revision";
    }
    
    identity southboundmanager-api {
        base "config:service-type";
        config:java-class "org.opendaylight.openflowplugin.applications.southboundmanager.openflowservice.api.IOpenflowFacade";
    }
}
