module admin-reconciliation {

    namespace "urn:opendaylight:params:xml:ns:yang:openflowplugin:app:admin-reconciliation:service";
    prefix admin-reconciliation;

    revision "2018-02-27" {
        description "Initial revision for admin reconciliation";
    }

    container reconciliation-counter {
        description "Number of administrative ordered reconciliation";
        list reconcile-counter {
            key node-id;
            uses counter;
        }
    }

    grouping counter {
        leaf node-id {
            type uint64;
        }
        leaf success-count {
            type uint32;
            default 0;
        }
        leaf failure-count {
            type uint32;
            default 0;
        }
        leaf last-request-time {
             description "Timestamp when admin reconcile was last requested";
             type string;
        }
    }

    rpc reconcile {
        description "Requests the execution of an administrative reconciliation between the controller and
                     one or several or all Nodes";
        input {
            leaf-list nodes {
                description "List of nodes to be reconciled";
                type uint64;
            }

            leaf reconcile-all-nodes {
                description "Flag to indicate that all nodes to be reconciled";
                type boolean;
                mandatory false;
                default false;
            }
        }

        output {
             leaf result {
                 type boolean;
             }
        }
    }
}
