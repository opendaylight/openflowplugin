module resync {

    namespace "urn:opendaylight:params:xml:ns:yang:openflowplugin:app:resync:service";
    prefix admin-resync;

    revision "2018-02-27" {
        description "Initial revision for admin reconciliation";
    }

    rpc exec-resync {

        input {
            leaf-list nodes {
                description "List of nodes to be reconciled";
                type uint64;
            }

            leaf reconcile-all-nodes {
                description "Flag to indicate that all nodes must be reconciled";
                type boolean;
                mandatory false;
                default false;
            }
        }

        output {
             leaf result {
                 type boolean;
             }
        }
    }
}
