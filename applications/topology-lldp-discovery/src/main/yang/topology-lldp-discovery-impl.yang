module topology-lldp-discovery-impl {
    yang-version 1;
    namespace "urn:opendaylight:params:xml:ns:yang:topology-lldp-discovery:impl";
    prefix "topology-lldp-discovery-impl";

    import config { prefix config; revision-date 2013-04-05; }
    import opendaylight-md-sal-binding { prefix md-sal-binding; revision-date 2013-10-28;}

    description
        "Service definition for topology-lldp-discovery";

    revision "2015-05-30" {
        description
            "Initial revision";
    }

    identity topology-lldp-discovery-impl {
        base config:module-type;
        config:java-name-prefix TopologyLldpDiscoveryImpl;
        status deprecated;
    }

    augment "/config:modules/config:module/config:configuration" {
        case topology-lldp-discovery-impl {
            when "/config:modules/config:module/config:type = 'topology-lldp-discovery-impl'";
            container broker {
                uses config:service-ref {
                    refine type {
                        mandatory true;
                        config:required-identity md-sal-binding:binding-broker-osgi-registry;
                    }
                }
            }
            leaf lldp-secure-key {
                description "Provided key will be used to generate LLDP custom security hash";
                type string;
            }
        }
    }
}
